module test-plugin {

	namespace "urn:ietf:params:xml:ns:yang:test-plugin";

	prefix "ts-pl";

	description
	    "This module is used for Sysrepo plugin testing.";

	revision "2018-02-20" {
	    description
	        "Version 0.1.0";
	}

    rpc call {

        input {
            leaf command {
                type string;
            }
        }

        output {
            leaf response {
                type string;
            }
        }
    }
}
